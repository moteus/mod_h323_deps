MEDIA-TRAVERSAL {itu-t(0) recommendation(0) h(8) 460 17 1} DEFINITIONS AUTOMATIC TAGS ::=

BEGIN

FrameData ::= CHOICE
{
    rtp         OCTET STRING (SIZE(12..1456)),
    rtcp        OCTET STRING (SIZE(1..1456))	
}

UDPFrame ::= SEQUENCE
{
   sessionId   INTEGER (0..255),
   dataFrame   BOOLEAN,
   frame       SEQUENCE OF FrameData
}

END
